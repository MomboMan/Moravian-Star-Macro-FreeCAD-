import math
import FreeCAD as App
import Part

def create_guaranteed_star(point_height=40.0, base_radius=10.0):
    """
    Creates a perfect 12-point symmetrical star using FreeCAD primitives
    that are guaranteed to display and fuse into a solid.
    """
    doc = App.activeDocument()
    if not doc:
        doc = App.newDocument("MoravianStar12_Solid")
        
    phi = (1.0 + math.sqrt(5.0)) / 2.0
    
    # 1. Create a 4-sided pyramid pointing straight up (Z-axis) using a 4-segmented cone
    # This is 100% solid, fully closed, and visually reliable
    single_point = Part.makeCone(base_radius, 0, point_height, App.Vector(0,0,0), App.Vector(0,0,1), 360)
    single_point = single_point.polygon(4) # Force it to be a sharp 4-sided pyramid
    
    # 2. Define the exact geometric orientation axes for a 12-point star layout
    axes = [
        (0, 1, phi),   (0, 1, -phi),  (0, -1, phi),  (0, -1, -phi),
        (1, phi, 0),   (1, -phi, 0),  (-1, phi, 0),  (-1, -phi, 0),
        (phi, 0, 1),   (phi, 0, -1),  (-phi, 0, 1),  (-phi, 0, -1)
    ]
    
    star_shape = None
    
    # 3. Rotate and position a solid spike in all 12 positions
    for ax in axes:
        # Create target direction vector
        target_dir = App.Vector(ax[0], ax[1], ax[2]).normalize()
        
        # Clone our perfect solid spike
        spike = single_point.copy()
        
        # Calculate the proper 3D rotation angle
        z_axis = App.Vector(0, 0, 1)
        rot_axis = z_axis.cross(target_dir)
        
        if rot_axis.Length > 0.0001:
            rot_axis.normalize()
            angle = math.degrees(math.acos(z_axis.dot(target_dir)))
            spike.rotate(App.Vector(0,0,0), rot_axis, angle)
            
        # Combine everything cleanly
        if star_shape is None:
            star_shape = spike
        else:
            star_shape = star_shape.fuse(spike)
            
    # 4. Output the solid star straight to your project window
    star_obj = doc.addObject("Part::Feature", "MoravianStar12_Solid")
    star_obj.Shape = star_shape
    doc.recompute()
    
    # Force view refresh so you see it instantly
    if App.GuiUp:
        App.Gui.ActiveDocument.ActiveView.fitAll()

# Execute code
create_guaranteed_star(point_height=45.0, base_radius=12.0)

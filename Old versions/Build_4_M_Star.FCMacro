import math
import FreeCAD as App
import Part
from PySide import QtWidgets, QtCore

class MoravianStarDialog(QtWidgets.QDialog):
    def __init__(self):
        super(MoravianStarDialog, self).__init__()
        self.init_ui()
        
    def init_ui(self):
        self.setWindowTitle("12-Point Moravian Star Generator")
        self.resize(320, 200)
        
        # Main vertical layout
        layout = QtWidgets.QVBoxLayout()
        grid = QtWidgets.QGridLayout()
        
        # Form inputs: Labels & SpinBoxes
        grid.addWidget(QtWidgets.QLabel("Base Radius (mm):"), 0, 0)
        self.radius_input = QtWidgets.QDoubleSpinBox()
        self.radius_input.setRange(1.0, 500.0)
        self.radius_input.setValue(2.5)
        grid.addWidget(self.radius_input, 0, 1)
        
        grid.addWidget(QtWidgets.QLabel("Spike Height (mm):"), 1, 0)
        self.height_input = QtWidgets.QDoubleSpinBox()
        self.height_input.setRange(1.0, 1000.0)
        self.height_input.setValue(20.0)
        grid.addWidget(self.height_input, 1, 1)
        
        grid.addWidget(QtWidgets.QLabel("Sides:"), 2, 0)
        self.sides_input = QtWidgets.QSpinBox()
        self.sides_input.setRange(3, 20)
        self.sides_input.setValue(5)
        grid.addWidget(self.sides_input, 2, 1)
        
        grid.addWidget(QtWidgets.QLabel("Mount Hole Diameter (mm):"), 3, 0)
        self.hole_dia_input = QtWidgets.QDoubleSpinBox()
        self.hole_dia_input.setRange(0.0, 200.0)
        self.hole_dia_input.setValue(2.5)
        grid.addWidget(self.hole_dia_input, 3, 1)
        
        grid.addWidget(QtWidgets.QLabel("Mount Hole Depth (mm):"), 4, 0)
        self.hole_depth_input = QtWidgets.QDoubleSpinBox()
        self.hole_depth_input.setRange(0.0, 500.0)
        self.hole_depth_input.setValue(3.75)
        grid.addWidget(self.hole_depth_input, 4, 1)
        
        layout.addLayout(grid)
        
        # Action Button
        self.generate_btn = QtWidgets.QPushButton("Generate Star")
        self.generate_btn.clicked.connect(self.on_generate)
        layout.addWidget(self.generate_btn)
        
        self.setLayout(layout)
        
    def on_generate(self):
        # Extract fresh numbers directly from the input fields
        r = self.radius_input.value()
        h = self.height_input.value()
        sides = self.sides_input.value()
        h_dia = self.hole_dia_input.value()
        h_depth = self.hole_depth_input.value()
        
        # Call our solid structural core engine
        build_mountable_12_point_star(r, h, sides, h_dia, h_depth)
        self.accept() # Close window smoothly after rendering

    def on_generate(self):
        r = self.radius_input.value()
        h = self.height_input.value()
        sides = self.sides_input.value()
        h_dia = self.hole_dia_input.value()
        h_depth = self.hole_depth_input.value()
        
        build_clean_star(r, h, sides, h_dia, h_depth)
        self.accept()

def build_clean_star(base_radius, point_height, sides, hole_diameter, hole_depth):
    doc = App.activeDocument()
    if not doc:
        doc = App.newDocument("MoravianStar_Clean")
      
    try:
        phi = (1.0 + math.sqrt(5.0)) / 2.0  # Proper icosahedral Golden Ratio constant
        
        true_12_axes = [
            (0, 1, phi),   (0, 1, -phi),  (0, -1, phi),  (0, -1, -phi),
            (1, phi, 0),   (1, -phi, 0),  (-1, phi, 0),  (-1, -phi, 0),
            (phi, 0, 1),   (phi, 0, -1),  (-phi, 0, 1),  (-phi, 0, -1)
        ]
        
        star_points = []
        
        # 1. Project the structural apex points out in space
        for ax in true_12_axes:
            ax_x, ax_y, ax_z = ax[0], ax[1], ax[2]
            vec = App.Vector(ax_x, ax_y, ax_z).normalize()
            # The tip of each spike extends to point_height
            tip_vec = vec * point_height
            star_points.append(Part.Vertex(tip_vec))
            
            # For shapes like sides=4+, intermediate valleys are needed, 
            # but for sides=3, a clean star shape matches the pure icosahedron vertices.
            if sides > 3:
                # Add a tiny internal core vertex for geometry blending if needed
                core_vec = vec * base_radius
                star_points.append(Part.Vertex(core_vec))

        # 2. Build the perfectly flat, clean manifold outer shape using a Convex Hull
        star_shape = Part.makeConvexHull(star_points)
        
        # 3. Cut out the post pocket cleanly
        if hole_diameter > 0 and hole_depth > 0:
            hole_radius = hole_diameter / 2.0
            # Sinking the tool deep ensures a flat bottom cut at the star base
            mount_tool = Part.makeCylinder(hole_radius, hole_depth + 10, App.Vector(0, 0, -(hole_depth + 5)), App.Vector(0, 0, 1), 360)
            star_shape = star_shape.cut(mount_tool)
        
        # 4. Push to document tree
        star_feature = doc.addObject("Part::Feature", "Moravian Star")
        star_feature.Shape = star_shape
        hole_radius = hole_diameter / 2.0 
        star_feature.Label = f"Clean-Star-{sides}S-{point_height}mm"
        doc.recompute()
        
        if App.GuiUp:
            import FreeCADGui as Gui
            Gui.ActiveDocument.ActiveView.fitAll()
            
        print("Success! Perfect mathematical star generated without artifacts.")
        
    except Exception as err:
        print("Generation failed: " + str(err))

# Launch dialog safely
dialog = MoravianStarDialog()
dialog.exec()

import math
import FreeCAD as App
import Part

def build_true_12_point_star(base_radius=10.0, point_height=45.0):
    doc = App.activeDocument()
    if not doc:
        doc = App.newDocument("MoravianStar12")
        
    try:
        phi = (1.0 + math.sqrt(5.0)) / 2.0
        
        # Symmetrical 3D directions for a true 12-point layout
        true_12_axes = [
            (0, 1, phi),   (0, 1, -phi),  (0, -1, phi),  (0, -1, -phi),
            (1, phi, 0),   (1, -phi, 0),  (-1, phi, 0),  (-1, -phi, 0),
            (phi, 0, 1),   (phi, 0, -1),  (-phi, 0, 1),  (-phi, 0, -1)
        ]
        
        # 1. Build a sharp, solid 5-sided pyramid pointing straight up (Z-axis)
        # Create the 5 outer corner points of the pentagonal base
        base_verts = []
        for i in range(5):
            angle = i * (2 * math.pi / 5.0)
            x = base_radius * math.cos(angle)
            y = base_radius * math.sin(angle)
            base_verts.append(App.Vector(x, y, 0))
            
        tip = App.Vector(0, 0, point_height)
        pyramid_faces = []
        
        # Build the 5 triangular sides of the star point
        for i in range(5):
            v1 = base_verts[i]
            v2 = base_verts[(i + 1) % 5]
            wire = Part.Wire([Part.makeLine(v1, v2), Part.makeLine(v2, tip), Part.makeLine(tip, v1)])
            pyramid_faces.append(Part.Face(wire))
            
        # Build the 1 flat pentagonal bottom face to seal it tight
        base_edges = [Part.makeLine(base_verts[i], base_verts[(i + 1) % 5]) for i in range(5)]
        pyramid_faces.append(Part.Face(Part.Wire(base_edges)))
        
        # Sew the faces into a single watertight solid point
        single_point = Part.makeSolid(Part.makeShell(pyramid_faces))
        
        fused_shape = None
        
        # 2. Duplicate, rotate, and fuse the points into the 12 spatial directions
        for ax in true_12_axes:
            target_direction = App.Vector(ax[0], ax[1], ax[2]).normalize()
            
            spike = single_point.copy()
            
            z_axis = App.Vector(0, 0, 1)
            rotation_axis = z_axis.cross(target_direction)
            
            if rotation_axis.Length > 0.0001:
                rotation_axis.normalize()
                angle_deg = math.degrees(math.acos(z_axis.dot(target_direction)))
                spike.rotate(App.Vector(0,0,0), rotation_axis, angle_deg)
                
            if fused_shape is None:
                fused_shape = spike
            else:
                fused_shape = fused_shape.fuse(spike)
                
        # 3. Output the finalized solid geometry straight to the workspace tree
        star_feature = doc.addObject("Part::Feature", "True_Moravian_Star_12")
        star_feature.Shape = fused_shape
        doc.recompute()
        
        if App.GuiUp:
            import FreeCADGui as Gui
            Gui.ActiveDocument.ActiveView.fitAll()
            
        print("Success! The sharp 12-point solid star has generated cleanly.")
        
    except Exception as err:
        print("Generation failed: " + str(err))

# Run the fixed structural script
build_true_12_point_star(base_radius=10.0, point_height=40.0)

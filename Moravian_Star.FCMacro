__Name__ = 'Moravian Star'
__Comment__ = 'A FreeCAD macro that creates a Moravian Star. It is a 12 point version of the star that is hollow.'
__Author__ = 'Craig Drinnan'
__Date__ = '2026-11-05'
__Version__ = '2.1 beta'
__License__ = 'GPL-3.0-or-later'
__Web__ = 'https://github.com/MomboMan/Moravian-Star-Macro-FreeCAD-'
__Wiki__ = ''
__Icon__ = ''
__Xpm__ = ''
__Help__ = ''
__Status__ = 'Stable'
__Requires__ = 'FreeCAD >= 26.3.0RC2 '
__Communication__ = 'https://github.com/MomboMan/Moravian-Star-Macro-FreeCAD-/issues'
__Files__ = ''

import math
import FreeCAD as App
import Part
from PySide import QtWidgets, QtCore

class MoravianStarDialog(QtWidgets.QDialog):
    def __init__(self):
        super(MoravianStarDialog, self).__init__()
        self.init_ui()
        
    def init_ui(self):
        widget=0
        self.setWindowTitle("12-Point Moravian Star Generator")
        self.resize(320, 260)
        
        layout = QtWidgets.QVBoxLayout()
        grid = QtWidgets.QGridLayout()
        
        grid.addWidget(QtWidgets.QLabel("Base Radius (mm):"), widget, 0)
        self.radius_input = QtWidgets.QDoubleSpinBox()
        self.radius_input.setRange(1.0, 500.0)
        self.radius_input.setValue(5.0)
        grid.addWidget(self.radius_input, widget, 1)
        widget += 1
        
        grid.addWidget(QtWidgets.QLabel("Spike Height (mm):"), widget, 0)
        self.height_input = QtWidgets.QDoubleSpinBox()
        self.height_input.setRange(1.0, 1000.0)
        self.height_input.setValue(40.0)
        grid.addWidget(self.height_input, widget, 1)
        widget += 1
        
        grid.addWidget(QtWidgets.QLabel("Sides:"), widget, 0)
        self.sides_input = QtWidgets.QSpinBox()
        self.sides_input.setRange(3, 20)
        self.sides_input.setValue(5)
        grid.addWidget(self.sides_input, widget, 1)
        widget += 1    

        grid.addWidget(QtWidgets.QLabel("Make Hollow:"), widget, 0)
        self.make_hollow = QtWidgets.QCheckBox()
        self.make_hollow.setChecked(True)
        self.make_hollow.stateChanged.connect(self.toggle_hollow_inputs)
        grid.addWidget(self.make_hollow, widget, 1)
        widget += 1    
                
        # UI addition for Wall Thickness
        self.wall_thickness_Label = QtWidgets.QLabel("Wall Thickness (mm):")
        grid.addWidget(self.wall_thickness_Label, widget, 0)
        self.thick_input = QtWidgets.QDoubleSpinBox()
        self.thick_input.setRange(0.2, 10.0)
        self.thick_input.setValue(1.2)
        grid.addWidget(self.thick_input, widget, 1)
        widget += 1    
        
        grid.addWidget(QtWidgets.QLabel("Create Mount Hole:"), widget, 0)
        self.create_mount_hole = QtWidgets.QCheckBox()
        self.create_mount_hole.setChecked(True)
        self.create_mount_hole.stateChanged.connect(self.toggle_hole_inputs)
        grid.addWidget(self.create_mount_hole, widget, 1)
        widget += 1    
        

        self.through_all_Label = QtWidgets.QLabel("Through All:")
        grid.addWidget(self.through_all_Label, widget, 0)
        self.through_all = QtWidgets.QCheckBox()
        self.through_all.setChecked(False)
        self.through_all.stateChanged.connect(self.through_all_inputs)
        grid.addWidget(self.through_all, widget, 1)
        widget += 1    
        
        self.mount_hole_dia_Label = QtWidgets.QLabel("Mount Hole Diameter (mm):")
        grid.addWidget(self.mount_hole_dia_Label, widget, 0)
        self.mount_hole_dia_input = QtWidgets.QDoubleSpinBox()
        self.mount_hole_dia_input.setRange(0.0, 200.0)
        self.mount_hole_dia_input.setValue(5.0)
        grid.addWidget(self.mount_hole_dia_input, widget, 1)
        widget += 1    
        
        self.hole_depth_Label = QtWidgets.QLabel("Mount Hole Depth (mm):")
        grid.addWidget(self.hole_depth_Label, widget, 0)
        self.hole_depth_input = QtWidgets.QDoubleSpinBox()
        self.hole_depth_input.setRange(0.0, 500.0)
        self.hole_depth_input.setValue(5.0)
        grid.addWidget(self.hole_depth_input, widget, 1)
        widget += 1    
        
        layout.addLayout(grid)
        
        self.generate_btn = QtWidgets.QPushButton("Generate Star")
        self.generate_btn.clicked.connect(self.on_generate)
        layout.addWidget(self.generate_btn)
        
        self.setLayout(layout)
        
    def toggle_hollow_inputs(self, state:bool):
        self.wall_thickness_Label.setEnabled(state)
        self.thick_input.setEnabled(state)
        
    def toggle_hole_inputs(self, state):
        if self.create_mount_hole.isChecked():
            self.through_all_Label.setEnabled(True)
            self.through_all.setEnabled(True)
            self.hole_depth_Label.setEnabled(True)
            self.hole_depth_input.setEnabled(True)
            self.mount_hole_dia_Label.setEnabled(True)
            self.mount_hole_dia_input.setEnabled(True)
            if self.through_all.isChecked():
                self.hole_depth_Label.setEnabled(False)
                self.hole_depth_input.setEnabled(False)
            else:
                self.hole_depth_Label.setEnabled(True)
                self.hole_depth_input.setEnabled(True)
        else:
            self.through_all_Label.setEnabled(False)
            self.through_all.setEnabled(False)
            self.mount_hole_dia_Label.setEnabled(False)
            self.mount_hole_dia_input.setEnabled(False)
            self.hole_depth_Label.setEnabled(False)
            self.hole_depth_input.setEnabled(False)

            
    def through_all_inputs(self, state):
        self.hole_depth_Label.setEnabled(not state)
        self.hole_depth_input.setEnabled(not state)
        
        
    def on_generate(self):
        r = self.radius_input.value()
        h = self.height_input.value()
        sides = self.sides_input.value()
        hollow = self.make_hollow.isChecked()
        if hollow:
            thick = self.thick_input.value()
        else:
            thick = 0.0
                
        if self.create_mount_hole.isChecked():
            h_dia = self.mount_hole_dia_input.value()
            h_depth = self.hole_depth_input.value()
        else:
            h_dia = 0.0
            h_depth = 0.0
        
        build_mountable_12_point_star(r, h, sides, h_dia, h_depth, thick, hollow)
        self.accept() 

def build_mountable_12_point_star(base_radius, point_height, sides, hole_diameter, hole_depth, 
    wall_thickness, hollow):
    doc = App.activeDocument()
    if not doc:
        doc = App.newDocument("MoravianStar12")
      
    try:
        phi = (1.0 + math.sqrt(5.0)) / 2.0
        
        true_12_axes = [
            (0, 1, phi),   (0, 1, -phi),  (0, -1, phi),  (0, -1, -phi),
            (1, phi, 0),   (1, -phi, 0),  (-1, phi, 0),  (-1, -phi, 0),
            (phi, 0, 1),   (phi, 0, -1),  (-phi, 0, 1),  (-phi, 0, -1)
        ]
        
        # 1A. Build the solid outer spike pyramid
        base_verts = []
        for i in range(sides):
            angle = i * (2 * math.pi / sides)
            x_val = base_radius * math.cos(angle)
            y_val = base_radius * math.sin(angle)
            z_val = -base_radius * 0.5 if sides == 3 else 0.0
            base_verts.append(App.Vector(x_val, y_val, z_val))
            
        tip = App.Vector(0, 0, point_height)
        pyramid_faces = []
        for i in range(sides):
            v1 = base_verts[i]
            v2 = base_verts[(i + 1) % sides]
            wire = Part.Wire([Part.makeLine(v1, v2), Part.makeLine(v2, tip), Part.makeLine(tip, v1)])
            pyramid_faces.append(Part.Face(wire))
            
        base_edges = [Part.makeLine(base_verts[i], base_verts[(i + 1) % sides]) for i in range(sides)]
        pyramid_faces.append(Part.Face(Part.Wire(base_edges)))
        outer_spike = Part.makeSolid(Part.makeShell(pyramid_faces))
        
        # 1B. Build a smaller inner pyramid tool to clear out the core
        # Scale down the radius and height proportionally based on the wall thickness
        scale_r = max(0.1, base_radius - wall_thickness)
        scale_h = max(1.0, point_height - wall_thickness)
        
        inner_verts = []
        for i in range(sides):
            angle = i * (2 * math.pi / sides)
            x_val = scale_r * math.cos(angle)
            y_val = scale_r * math.sin(angle)
            z_val = (-base_radius * 0.5) - 1.0 if sides == 3 else -1.0 # Extend slightly past base to ensure clear entry
            inner_verts.append(App.Vector(x_val, y_val, z_val))
            
        if hollow:
            inner_tip = App.Vector(0, 0, scale_h)
            inner_faces = []
            for i in range(sides):
                v1 = inner_verts[i]
                v2 = inner_verts[(i + 1) % sides]
                wire = Part.Wire([Part.makeLine(v1, v2), Part.makeLine(v2, inner_tip), Part.makeLine(inner_tip, v1)])
                inner_faces.append(Part.Face(wire))
                
            inner_base_edges = [Part.makeLine(inner_verts[i], inner_verts[(i + 1) % sides]) for i in range(sides)]
            inner_faces.append(Part.Face(Part.Wire(inner_base_edges)))
            inner_void_tool = Part.makeSolid(Part.makeShell(inner_faces))
        
            # Cut the inner out of the outer to form a true hollow cup
            single_point = outer_spike.cut(inner_void_tool)
        else:
            single_point = outer_spike #.cut(inner_void_tool)
        
        star_shape = None
        
        # 2. Duplicate, rotate, and fuse the hollow cups into the 12 spatial directions
        for ax in true_12_axes:
            ax_x, ax_y, ax_z = ax[0], ax[1], ax[2]
            target_direction = App.Vector(ax_x, ax_y, ax_z).normalize()
                
            spike = single_point.copy()
            z_axis = App.Vector(0, 0, 1)
            rotation_axis = z_axis.cross(target_direction)
                
            if rotation_axis.Length > 0.0001:
                rotation_axis.normalize()
                angle_deg = math.degrees(math.acos(z_axis.dot(target_direction)))
                spike.rotate(App.Vector(0,0,0), rotation_axis, angle_deg)
                
            if star_shape is None:
                star_shape = spike
            else:
                star_shape = star_shape.fuse(spike)
                       
        # 3. Cut out the post pocket if size parameters are greater than 0
        if hole_diameter > 0 and hole_depth > 0:
            hole_radius = hole_diameter / 2.0
            # mount_tool = Part.makeCylinder(hole_radius, hole_depth*2, App.Vector(0, 0, -hole_depth*2), App.Vector(0, 0, 1), 360)
            mount_tool = Part.makeCylinder(hole_radius, hole_depth*20, App.Vector(0, 0, -hole_depth*10), App.Vector(0, 0, 1), 360)
            star_shape = star_shape.cut(mount_tool)
        
        # 4. Output geometry straight to document tree
        star_feature = doc.addObject("Part::Feature", "MoravianStarShape")
        star_feature.Shape = star_shape
        star_feature.addProperty("App::PropertyLength", "Radius", "Dimensions", "Radius of the Star")
        star_feature.Radius = base_radius
        star_feature.setPropertyStatus("Radius", ["ReadOnly", "Output"]) 
        star_feature.addProperty("App::PropertyLength", "SpikeHeight", "Dimensions", "Height of each spike")
        star_feature.SpikeHeight = point_height
        star_feature.setPropertyStatus("SpikeHeight", ["ReadOnly", "Output"]) 
        star_feature.addProperty("App::PropertyInteger", "Sides", "Dimensions", "Sides on each spike")
        star_feature.Sides = sides
        star_feature.setPropertyStatus("Sides", ["ReadOnly", "Output"]) 
        star_feature.addProperty("App::PropertyLength", "HoleDiameter", "Dimensions", "Hole Diameter")
        star_feature.HoleDiameter = hole_diameter
        star_feature.setPropertyStatus("HoleDiameter", ["ReadOnly", "Output"]) 
        star_feature.addProperty("App::PropertyLength", "HoleDepth", "Dimensions", "Hole Depth")
        star_feature.HoleDepth = hole_depth
        star_feature.setPropertyStatus("HoleDepth", ["ReadOnly", "Output"]) 
        star_feature.addProperty("App::PropertyLength", "WallThickness", "Dimensions", "Wall Thickness")
        star_feature.WallThickness = wall_thickness
        star_feature.setPropertyStatus("WallThickness", ["ReadOnly", "Output"]) 
        star_feature.addProperty("App::PropertyString", "Version", "Base", "Created by Version")
        star_feature.Version = __Version__
        star_feature.setPropertyStatus("Version", ["ReadOnly", "Output"]) 
        body = doc.addObject("PartDesign::Body", "MoravianStarBody")
        if hole_diameter > 0 or hole_depth > 0:
            body.Label = "M-Star(" + str(sides) + ") " + str(base_radius) + " br " + str(point_height) + " sh " + str(hole_radius) + " hdia " + str(hole_depth) + " hdep"
        else:
            body.Label = "M-Star(" + str(sides) + ") " + str(base_radius) + " br " + str(point_height) + " sh"
            
        body.Group = [star_feature]
        doc.recompute()
        
        if App.GuiUp:
            import FreeCADGui as Gui
            Gui.ActiveDocument.ActiveView.fitAll()
            Gui.Selection.clearSelection()
            
    except Exception as err:
        print("Generation failed: " + str(err))
        
      

# Launch dialog safely
dialog = MoravianStarDialog()
dialog.exec()
